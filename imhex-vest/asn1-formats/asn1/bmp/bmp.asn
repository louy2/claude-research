-- Generated from an ImHex pattern by hexpat's ASN.1/ACN emitter.
Bmp-Module DEFINITIONS AUTOMATIC TAGS ::= BEGIN

BitmapFileHeader ::= SEQUENCE {
    signature OCTET STRING (SIZE(2)),
    fileSize INTEGER (0..4294967295),
    reserved1 INTEGER (0..65535),
    reserved2 INTEGER (0..65535),
    pixelDataOffset INTEGER (0..4294967295)
}

-- enum: RGB = 0, RLE8 = 1, RLE4 = 2, Bitfields = 3, JPEG = 4, PNG = 5
Compression-T ::= INTEGER (0..4294967295)

BitmapInfoHeader ::= SEQUENCE {
    headerSize INTEGER (0..4294967295),
    width INTEGER (0..4294967295),
    height INTEGER (0..4294967295),
    planes INTEGER (0..65535),
    bitsPerPixel INTEGER (0..65535),
    compression Compression-T,
    imageSize INTEGER (0..4294967295),
    xPixelsPerMeter INTEGER (0..4294967295),
    yPixelsPerMeter INTEGER (0..4294967295),
    colorsUsed INTEGER (0..4294967295),
    importantColors INTEGER (0..4294967295)
}

Bmp ::= SEQUENCE {
    file BitmapFileHeader,
    info BitmapInfoHeader
}

END
