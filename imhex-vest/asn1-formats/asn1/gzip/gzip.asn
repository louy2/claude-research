-- Generated from an ImHex pattern by hexpat's ASN.1/ACN emitter.
Gzip-Module DEFINITIONS AUTOMATIC TAGS ::= BEGIN

Flags-T ::= SEQUENCE {
    padding1 INTEGER (0..7),
    comment INTEGER (0..1),
    name INTEGER (0..1),
    extra INTEGER (0..1),
    hcrc INTEGER (0..1),
    text INTEGER (0..1)
}

-- enum: Fat = 0, Amiga = 1, Vms = 2, Unix = 3, Macintosh = 7, Ntfs = 11, Unknown = 255
Os-T ::= INTEGER (0..255)

Gzip ::= SEQUENCE {
    id1 INTEGER (0..255),
    id2 INTEGER (0..255),
    compressionMethod INTEGER (0..255),
    flags Flags-T,
    mtime INTEGER (0..4294967295),
    extraFlags INTEGER (0..255),
    os Os-T
}

END
