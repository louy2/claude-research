-- Generated from an ImHex pattern by hexpat's ASN.1/ACN emitter.
Qoi-Module DEFINITIONS AUTOMATIC TAGS ::= BEGIN

-- enum: RGB = 3, RGBA = 4
Channels-T ::= INTEGER (0..255)

-- enum: SRGB = 0, Linear = 1
Colorspace-T ::= INTEGER (0..255)

Qoi ::= SEQUENCE {
    magic INTEGER (1903126886), -- magic "qoif"
    width INTEGER (0..4294967295),
    height INTEGER (0..4294967295),
    channels Channels-T,
    colorspace Colorspace-T
}

END
