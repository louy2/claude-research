-- Generated from an ImHex pattern by hexpat's ASN.1/ACN emitter.
Zip-Module DEFINITIONS AUTOMATIC TAGS ::= BEGIN

-- enum: Stored = 0, Deflated = 8, Bzip2 = 12, Lzma = 14, Zstd = 93
Method-T ::= INTEGER (0..65535)

LocalFileHeader ::= SEQUENCE {
    signature OCTET STRING (SIZE(4)),
    version INTEGER (0..65535),
    flags INTEGER (0..65535),
    method Method-T,
    modTime INTEGER (0..65535),
    modDate INTEGER (0..65535),
    crc32 INTEGER (0..4294967295),
    uncompressedSize INTEGER (0..4294967295),
    name OCTET STRING (SIZE(0..65535)),
    extra OCTET STRING (SIZE(0..65535)),
    data OCTET STRING (SIZE(0..1048576))
}

-- the trailing `entries` array (until the end of the input) is decoded by the caller
Zip ::= SEQUENCE { }

END
